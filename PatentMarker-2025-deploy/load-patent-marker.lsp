; PatentMarker 2025 fallback loader. Generated by install-2025.ps1.
; Load this file with AutoCAD APPLOAD, or add it to the Startup Suite.
(defun c:PATENTMARKER-LOAD (/ dllPath oldFileDia)
  (setq dllPath "C:\\Users\\wjm\\WorkBuddy\\2026-06-20-00-50-28\\PatentMarker-2025-deploy\\PatentMarker.dll")
  (setq oldFileDia (getvar "FILEDIA"))
  (setvar "FILEDIA" 0)
  (command "_.NETLOAD" dllPath)
  (setvar "FILEDIA" oldFileDia)
  (princ "\nPatentMarker NETLOAD attempted. Use BZ to open the palette.")
  (princ)
)
(PATENTMARKER-LOAD)
(princ)
